; ; автор Фишман Денис в рамках проекта WF  12-02-2023 
(defun  C:PL100 (/ x1 x2 x3)
(vl-load-com)
 (command "_.-layer" "_m" "1091-III-D3-K15" "")
(command "_.3Dpoly" '(206236	-47787	0)'(95377	52133	0) "")
 (command "_.-layer" "_m" "1091-III-D4-K16" "")
(command "_.3Dpoly" '(206236	-47787	0)'(95377	52133	0) "")
 (command "_.-layer" "_m" "1091-III-D1-K13" "")
(command "_.3Dpoly" '(206236	-47787	0)'(95377	52133	0) "")
 (command "_.-layer" "_m" "1091-III-D2-K14" "")
(command "_.3Dpoly" '(206236	-47787	0)'(95377	52133	0) "")
 (command "_.-layer" "_m" "1091-III-V1-K24" "")
(command "_.3Dpoly" '(206236	-47787	0)'(95377	52133	0) "")
 (command "_.-layer" "_m" "1091-III-V4-K27" "")
(command "_.3Dpoly" '(206236	-47787	0)'(95377	52133	0) "")
 (command "_.-layer" "_m" "1091-III-DT-K28" "")
(command "_.3Dpoly" '(206236	-47787	0)'(95377	52133	0) "")
 (command "_.-layer" "_m" "1091-III-V2-K25" "")
(command "_.3Dpoly" '(206236	-47787	0)'(95377	52133	0) "")
 (command "_.-layer" "_m" "1091-III-V3-K26" "")
(command "_.3Dpoly" '(206236	-47787	0)'(95377	52133	0) "")
 (command "_.-layer" "_m" "1091-III-И4-K6" "")
(command "_.3Dpoly" '(206236	-47787	0)'(95377	52133	0) "")
 (command "_.-layer" "_m" "1091-III-P1-K7" "")
(command "_.3Dpoly" '(206236	-47787	0)'(95377	52133	0) "")
 (command "_.-layer" "_m" "1091-III-И2-K4" "")
(command "_.3Dpoly" '(206236	-47787	0)'(95377	52133	0) "")
 (command "_.-layer" "_m" "1091-III-И3-K5" "")
(command "_.3Dpoly" '(206236	-47787	0)'(95377	52133	0) "")
 (command "_.-layer" "_m" "1091-III-P2-K8" "")
(command "_.3Dpoly" '(206236	-47787	0)'(95377	52133	0) "")
 (command "_.-layer" "_m" "1091-III-V5-K11" "")
(command "_.3Dpoly" '(206236	-47787	0)'(95377	52133	0) "")
 (command "_.-layer" "_m" "1091-III-V6-K12" "")
(command "_.3Dpoly" '(206236	-47787	0)'(95377	52133	0) "")
 (command "_.-layer" "_m" "1091-III-P3-K9" "")
(command "_.3Dpoly" '(206236	-47787	0)'(95377	52133	0) "")
 (command "_.-layer" "_m" "1091-III-P4-K10" "")
(command "_.3Dpoly" '(206236	-47787	0)'(95377	52133	0) "")
 (command "_.-layer" "_m" "1091-III-FT-K30" "")
(command "_.3Dpoly" '(206236	-47787	0)'(95377	52133	0) "")
 (command "_.-layer" "_m" "1091-II-И2-K4" "")
(command "_.3Dpoly" '(206486	-40584	0)'(95377	55822	0) "")
 (command "_.-layer" "_m" "1091-II-И3-K5" "")
(command "_.3Dpoly" '(206486	-40584	0)'(95377	55822	0) "")
 (command "_.-layer" "_m" "1091-II-M1-K2" "")
(command "_.3Dpoly" '(206486	-40584	0)'(95377	55822	0) "")
 (command "_.-layer" "_m" "1091-II-И1-K3" "")
(command "_.3Dpoly" '(206486	-40584	0)'(95377	55822	0) "")
 (command "_.-layer" "_m" "1091-III-LT1-K31" "")
(command "_.3Dpoly" '(206236	-47787	0)'(95377	52133	0) "")
 (command "_.-layer" "_m" "1091-III-LT2-K32" "")
(command "_.3Dpoly" '(206236	-47787	0)'(95377	52133	0) "")
 (command "_.-layer" "_m" "1091-IV-D1-K13" "")
(command "_.3Dpoly" '(207351	-58292	0)'(95377	49490	0) "")
 (command "_.-layer" "_m" "1091-IV-D2-K14" "")
(command "_.3Dpoly" '(207351	-58292	0)'(95377	49490	0) "")
 (command "_.-layer" "_m" "1091-IV-V5-K11" "")
(command "_.3Dpoly" '(207351	-58292	0)'(95377	49490	0) "")
 (command "_.-layer" "_m" "1091-IV-V6-K12" "")
(command "_.3Dpoly" '(207351	-58292	0)'(95377	49490	0) "")
 (command "_.-layer" "_m" "1091-IV-D3-K15" "")
(command "_.3Dpoly" '(207351	-58292	0)'(95377	49490	0) "")
 (command "_.-layer" "_m" "1091-IV-V2-K25" "")
(command "_.3Dpoly" '(207351	-58292	0)'(95377	49490	0) "")
 (command "_.-layer" "_m" "1091-IV-V3-K26" "")
(command "_.3Dpoly" '(207351	-58292	0)'(95377	49490	0) "")
 (command "_.-layer" "_m" "1091-IV-D4-K16" "")
(command "_.3Dpoly" '(207351	-58292	0)'(95377	49490	0) "")
 (command "_.-layer" "_m" "1091-IV-V1-K24" "")
(command "_.3Dpoly" '(207351	-58292	0)'(95377	49490	0) "")
 (command "_.-layer" "_m" "1091-IV-И2-K4" "")
(command "_.3Dpoly" '(207351	-58292	0)'(95377	49490	0) "")
 (command "_.-layer" "_m" "1091-IV-И3-K5" "")
(command "_.3Dpoly" '(207351	-58292	0)'(95377	49490	0) "")
 (command "_.-layer" "_m" "1091-IV-M1-K2" "")
(command "_.3Dpoly" '(207351	-58292	0)'(95377	49490	0) "")
 (command "_.-layer" "_m" "1091-IV-И1-K3" "")
(command "_.3Dpoly" '(207351	-58292	0)'(95377	49490	0) "")
 (command "_.-layer" "_m" "1091-IV-И4-K6" "")
(command "_.3Dpoly" '(207351	-58292	0)'(95377	49490	0) "")
 (command "_.-layer" "_m" "1091-IV-P3-K9" "")
(command "_.3Dpoly" '(207351	-58292	0)'(95377	49490	0) "")
 (command "_.-layer" "_m" "1091-IV-P4-K10" "")
(command "_.3Dpoly" '(207351	-58292	0)'(95377	49490	0) "")
 (command "_.-layer" "_m" "1091-IV-P1-K7" "")
(command "_.3Dpoly" '(207351	-58292	0)'(95377	49490	0) "")
 (command "_.-layer" "_m" "1091-IV-P2-K8" "")
(command "_.3Dpoly" '(207351	-58292	0)'(95377	49490	0) "")
 (command "_.-layer" "_m" "1091-IV-V4-K27" "")
(command "_.3Dpoly" '(207351	-58292	0)'(95377	49490	0) "")
 (command "_.-layer" "_m" "1091-III-M1-K2" "")
(command "_.3Dpoly" '(206236	-47787	0)'(95377	52133	0) "")
 (command "_.-layer" "_m" "1091-III-И1-K3" "")
(command "_.3Dpoly" '(206236	-47787	0)'(95377	52133	0) "")
 (command "_.-layer" "_m" "1091-IV-LT1-K31" "")
(command "_.3Dpoly" '(207351	-58292	0)'(95377	49490	0) "")
 (command "_.-layer" "_m" "1091-IV-LT2-K32" "")
(command "_.3Dpoly" '(207351	-58292	0)'(95377	49490	0) "")
 (command "_.-layer" "_m" "1091-IV-DT-K28" "")
(command "_.3Dpoly" '(207351	-58292	0)'(95377	49490	0) "")
 (command "_.-layer" "_m" "1091-IV-FT-K30" "")
(command "_.3Dpoly" '(207351	-58292	0)'(95377	49490	0) "")
 (command "_.-layer" "_m" "1091-I-V3-K26" "")
(command "_.3Dpoly" '(206760	-32291	0)'(95377	58754	0) "")
 (command "_.-layer" "_m" "1091-I-V4-K27" "")
(command "_.3Dpoly" '(206760	-32291	0)'(95377	58754	0) "")
 (command "_.-layer" "_m" "1091-I-V1-K24" "")
(command "_.3Dpoly" '(206760	-32291	0)'(95377	58754	0) "")
 (command "_.-layer" "_m" "1091-I-V2-K25" "")
(command "_.3Dpoly" '(206760	-32291	0)'(95377	58754	0) "")
 (command "_.-layer" "_m" "1091-I-DT-K28" "")
(command "_.3Dpoly" '(206760	-32291	0)'(95377	58754	0) "")
 (command "_.-layer" "_m" "1091-I-LT2-K32" "")
(command "_.3Dpoly" '(206760	-32291	0)'(95377	58754	0) "")
 (command "_.-layer" "_m" "1091-I-FT-K30" "")
(command "_.3Dpoly" '(206760	-32291	0)'(95377	58754	0) "")
 (command "_.-layer" "_m" "1091-I-LT1-K31" "")
(command "_.3Dpoly" '(206760	-32291	0)'(95377	58754	0) "")
 (command "_.-layer" "_m" "1091-I-P4-K10" "")
(command "_.3Dpoly" '(206760	-32291	0)'(95377	58754	0) "")
 (command "_.-layer" "_m" "1091-I-V5-K11" "")
(command "_.3Dpoly" '(206760	-32291	0)'(95377	58754	0) "")
 (command "_.-layer" "_m" "1091-I-P2-K8" "")
(command "_.3Dpoly" '(206760	-32291	0)'(95377	58754	0) "")
 (command "_.-layer" "_m" "1091-I-P3-K9" "")
(command "_.3Dpoly" '(206760	-32291	0)'(95377	58754	0) "")
 (command "_.-layer" "_m" "1091-I-V6-K12" "")
(command "_.3Dpoly" '(206760	-32291	0)'(95377	58754	0) "")
 (command "_.-layer" "_m" "1091-I-D3-K15" "")
(command "_.3Dpoly" '(206760	-32291	0)'(95377	58754	0) "")
 (command "_.-layer" "_m" "1091-I-D4-K16" "")
(command "_.3Dpoly" '(206760	-32291	0)'(95377	58754	0) "")
 (command "_.-layer" "_m" "1091-I-D1-K13" "")
(command "_.3Dpoly" '(206760	-32291	0)'(95377	58754	0) "")
 (command "_.-layer" "_m" "1091-I-D2-K14" "")
(command "_.3Dpoly" '(206760	-32291	0)'(95377	58754	0) "")
 (command "_.-layer" "_m" "1091-II-V1-K24" "")
(command "_.3Dpoly" '(206486	-40584	0)'(95377	55822	0) "")
 (command "_.-layer" "_m" "1091-II-V2-K25" "")
(command "_.3Dpoly" '(206486	-40584	0)'(95377	55822	0) "")
 (command "_.-layer" "_m" "1091-II-D3-K15" "")
(command "_.3Dpoly" '(206486	-40584	0)'(95377	55822	0) "")
 (command "_.-layer" "_m" "1091-II-D4-K16" "")
(command "_.3Dpoly" '(206486	-40584	0)'(95377	55822	0) "")
 (command "_.-layer" "_m" "1091-II-V3-K26" "")
(command "_.3Dpoly" '(206486	-40584	0)'(95377	55822	0) "")
 (command "_.-layer" "_m" "1091-II-FT-K30" "")
(command "_.3Dpoly" '(206486	-40584	0)'(95377	55822	0) "")
 (command "_.-layer" "_m" "1091-II-LT1-K31" "")
(command "_.3Dpoly" '(206486	-40584	0)'(95377	55822	0) "")
 (command "_.-layer" "_m" "1091-II-V4-K27" "")
(command "_.3Dpoly" '(206486	-40584	0)'(95377	55822	0) "")
 (command "_.-layer" "_m" "1091-II-DT-K28" "")
(command "_.3Dpoly" '(206486	-40584	0)'(95377	55822	0) "")
 (command "_.-layer" "_m" "1091-II-P2-K8" "")
(command "_.3Dpoly" '(206486	-40584	0)'(95377	55822	0) "")
 (command "_.-layer" "_m" "1091-II-P3-K9" "")
(command "_.3Dpoly" '(206486	-40584	0)'(95377	55822	0) "")
 (command "_.-layer" "_m" "1091-II-И4-K6" "")
(command "_.3Dpoly" '(206486	-40584	0)'(95377	55822	0) "")
 (command "_.-layer" "_m" "1091-II-P1-K7" "")
(command "_.3Dpoly" '(206486	-40584	0)'(95377	55822	0) "")
 (command "_.-layer" "_m" "1091-II-P4-K10" "")
(command "_.3Dpoly" '(206486	-40584	0)'(95377	55822	0) "")
 (command "_.-layer" "_m" "1091-II-D1-K13" "")
(command "_.3Dpoly" '(206486	-40584	0)'(95377	55822	0) "")
 (command "_.-layer" "_m" "1091-II-D2-K14" "")
(command "_.3Dpoly" '(206486	-40584	0)'(95377	55822	0) "")
 (command "_.-layer" "_m" "1091-II-V5-K11" "")
(command "_.3Dpoly" '(206486	-40584	0)'(95377	55822	0) "")
 (command "_.-layer" "_m" "1091-II-V6-K12" "")
(command "_.3Dpoly" '(206486	-40584	0)'(95377	55822	0) "")
 (command "_.-layer" "_m" "1091-II-LT2-K32" "")
(command "_.3Dpoly" '(206486	-40584	0)'(95377	55822	0) "")
 (command "_.-layer" "_m" "1091-I-M1-K2" "")
(command "_.3Dpoly" '(206760	-32291	0)'(95377	58754	0) "")
 (command "_.-layer" "_m" "1091-I-И1-K3" "")
(command "_.3Dpoly" '(206760	-32291	0)'(95377	58754	0) "")
 (command "_.-layer" "_m" "1091-I-И4-K6" "")
(command "_.3Dpoly" '(206760	-32291	0)'(95377	58754	0) "")
 (command "_.-layer" "_m" "1091-I-P1-K7" "")
(command "_.3Dpoly" '(206760	-32291	0)'(95377	58754	0) "")
 (command "_.-layer" "_m" "1091-I-И2-K4" "")
(command "_.3Dpoly" '(206760	-32291	0)'(95377	58754	0) "")
 (command "_.-layer" "_m" "1091-I-И3-K5" "")
(command "_.3Dpoly" '(206760	-32291	0)'(95377	58754	0) "")
)
